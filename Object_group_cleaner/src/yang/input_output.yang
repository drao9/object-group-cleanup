module input_output {
  namespace "http://example.com/input_output";
  prefix input_output;

  import tailf-ncs {
    prefix ncs;
  }
  import tailf-common {
    prefix tailf;
  }
  grouping output {
    leaf start_time {
      type string;
    }
    leaf end_time {
      type string;
    }
    leaf run_time {
      type string;
    }
    leaf stat {
      type string;
    }
    leaf number_of_orphaned {
      type uint32;
    }
    list orphaned_object_groups {
      leaf og_type {
        type string;
      }
      leaf object_group {
        type string;
      }
    }
  }
  grouping input {
    leaf device {
      type leafref {
        path "/ncs:devices/ncs:device/ncs:name";
      }
    }
  }
  grouping input_output {
    tailf:action cleanup {
      tailf:actionpoint Object_group_cleaner;
      tailf:info "Search and delete orphaned object groups from devices";
      input {
        uses input;
      }
      output {
        uses output;
      }
    }
    tailf:action search {
      tailf:actionpoint Object_group_cleaner;
      tailf:info "Search for orphaned object groups within devices without deleting any";
      input {
        uses input;
      }
      output {
        uses output;
      }
    }
    tailf:action remove {
      tailf:actionpoint Object_group_cleaner;
      tailf:info "Delete specific object groups from a device";
      input {
        leaf csv {
          type string;
        }
        list inputs {
          tailf:info "Input values for remove";
          leaf device_name {
            type string;
          }
          leaf og_type {
            type enumeration {
              enum "service";
              enum "network";
              enum "icmp-type";
              enum "user";
            }
          }
          leaf og_name {
            type string;
          }
        }
      }
      output {
        leaf start_time {
          type string;
        }
        leaf end_time {
          type string;
        }
        leaf run_time {
          type string;
        }
        list deleted_object_groups {
          leaf og_type {
            type string;
          }
          leaf object_group {
            type string;
          }
        }
        leaf stat {
          type string;
        }
      }
    }
  }
}
